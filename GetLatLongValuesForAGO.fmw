FME workspace GetLatLongValuesForAGO.fmw

Readers:
- ARCGISONLINEFEATURES_2: ARCGISONLINEFEATURES
- ARCGISONLINEFEATURES_1: ARCGISONLINEFEATURES

Writers:
- ARCGISONLINEFEATURES_3: ARCGISONLINEFEATURES to <Unused>

D6SPCheckSheet (reader ARCGISONLINEFEATURES_1)
    attributes: OBJECTID esriFieldTypeOID, PPSNbr esriFieldTypeString(255), PrjEngr esriFieldTypeString(255), TeamLdr esriFieldTypeString(255), CntrcNum esriFieldTypeString(255), DsgnJNum esriFieldTypeString(255), ConsJNum esriFieldTypeString(255), SctnNum esriFieldTypeString(255), SPLDate esriFieldTypeDate, SPPSDate esriFieldTypeDate, CstEstT esriFieldTypeString(255), CEDate esriFieldTypeDate, PEPrComp esriFieldTypeSmallInteger, PEICPrj esriFieldTypeString(255), PEConNam esriFieldTypeString(255), PERADate esriFieldTypeDate, PEPTBNum esriFieldTypeString(255), PrsntBMo esriFieldTypeString(255), BiMoDate esriFieldTypeDate, ESRRqrd esriFieldTypeString(255), ECSSubmt esriFieldTypeString(255), EnvCateg esriFieldTypeString(255), PESAReq esriFieldTypeString(255), PESADate esriFieldTypeDate, HydRpRqr esriFieldTypeString(255), HydApDate esriFieldTypeDate, IDSRqrd esriFieldTypeString(255), IDSInit esriFieldTypeString(255), IDSADate esriFieldTypeDate, BCRRqrd esriFieldTypeString(255),
      BCRSubmt esriFieldTypeString(255), BCRADate esriFieldTypeDate, PubInRqd esriFieldTypeString(255), UPlMuRqd esriFieldTypeString(255), UpRrjSup esriFieldTypeString(255), LOIRqrd esriFieldTypeString(255), LOISbmtd esriFieldTypeString(255), LOISDate esriFieldTypeDate, SigRoute esriFieldTypeString(255), TMPRqrd esriFieldTypeString(255), TMPCompl esriFieldTypeString(255), TMPAqrd esriFieldTypeString(255), TMACompl esriFieldTypeString(255), RdClosur esriFieldTypeString(255), SbmtDetr esriFieldTypeString(255), RdClsApr esriFieldTypeString(255), PE2PrComp esriFieldTypeSmallInteger, PE2ICPrj esriFieldTypeString(255), PE2CName esriFieldTypeString(255), PE2PDate esriFieldTypeDate, PE2PTBNu esriFieldTypeString(255), PrjPrntd esriFieldTypeString(255), GeoRqrd esriFieldTypeString(255), GeoInit esriFieldTypeString(255), GeoADate esriFieldTypeDate, TSLRqrd esriFieldTypeString(255), TSLADate esriFieldTypeDate, PrmtRqrd esriFieldTypeString(255), ApSbmtd esriFieldTypeString(255), PrmtDate esriFieldTypeDate,
      PSIRqrd esriFieldTypeString(255), ROWRqrd esriFieldTypeString(255), POLtrSnt esriFieldTypeString(255), ROWSbmtd esriFieldTypeString(255), ROWJobNu esriFieldTypeString(255), RRAgRqrd esriFieldTypeString(255), UtAgRqrd esriFieldTypeString(255), JnAgRqrd esriFieldTypeString(255), LtrUnRqd esriFieldTypeString(255), InLtrRqd esriFieldTypeString(255), Comments esriFieldTypeString(255), ImprvTyp esriFieldTypeString(255), NoROWRqd1 esriFieldTypeSmallInteger, NoROWAqd1 esriFieldTypeSmallInteger, CostEst1 esriFieldTypeInteger, MarkedRoute esriFieldTypeString(200), D6Area esriFieldTypeString(50), DistrictFiscalYear esriFieldTypeSmallInteger, CO_FY esriFieldTypeSmallInteger, ImprovementType esriFieldTypeString(255), GlobalID esriFieldTypeGlobalID(38), Latitude esriFieldTypeDouble, Longitude esriFieldTypeDouble
    -> Reprojector
Reprojector
    INTERPOLATION_TYPE_NAME = Nearest Neighbor
    RASTER_CELL_SIZE = Preserve Cells
    DEST = EPSG:4269
    SOURCE = Read from feature
    REPROJECTED -> CoordinateExtractor_2
CoordinateExtractor_2
    MODE = Specify Coordinate
    IND = 0
    X_ATTR = _xLong
    Y_ATTR = _yLat
    -> D6SPCheckSheet (writer ARCGISONLINEFEATURES_3)
D6SPCheckSheet (writer ARCGISONLINEFEATURES_3)
    attributes: OBJECTID esriFieldTypeOID, PPSNbr esriFieldTypeString(255), PrjEngr esriFieldTypeString(255), TeamLdr esriFieldTypeString(255), CntrcNum esriFieldTypeString(255), DsgnJNum esriFieldTypeString(255), ConsJNum esriFieldTypeString(255), SctnNum esriFieldTypeString(255), SPLDate esriFieldTypeDate, SPPSDate esriFieldTypeDate, CstEstT esriFieldTypeString(255), CEDate esriFieldTypeDate, PEPrComp esriFieldTypeSmallInteger, PEICPrj esriFieldTypeString(255), PEConNam esriFieldTypeString(255), PERADate esriFieldTypeDate, PEPTBNum esriFieldTypeString(255), PrsntBMo esriFieldTypeString(255), BiMoDate esriFieldTypeDate, ESRRqrd esriFieldTypeString(255), ECSSubmt esriFieldTypeString(255), EnvCateg esriFieldTypeString(255), PESAReq esriFieldTypeString(255), PESADate esriFieldTypeDate, HydRpRqr esriFieldTypeString(255), HydApDate esriFieldTypeDate, IDSRqrd esriFieldTypeString(255), IDSInit esriFieldTypeString(255), IDSADate esriFieldTypeDate, BCRRqrd esriFieldTypeString(255),
      BCRSubmt esriFieldTypeString(255), BCRADate esriFieldTypeDate, PubInRqd esriFieldTypeString(255), UPlMuRqd esriFieldTypeString(255), UpRrjSup esriFieldTypeString(255), LOIRqrd esriFieldTypeString(255), LOISbmtd esriFieldTypeString(255), LOISDate esriFieldTypeDate, SigRoute esriFieldTypeString(255), TMPRqrd esriFieldTypeString(255), TMPCompl esriFieldTypeString(255), TMPAqrd esriFieldTypeString(255), TMACompl esriFieldTypeString(255), RdClosur esriFieldTypeString(255), SbmtDetr esriFieldTypeString(255), RdClsApr esriFieldTypeString(255), PE2PrComp esriFieldTypeSmallInteger, PE2ICPrj esriFieldTypeString(255), PE2CName esriFieldTypeString(255), PE2PDate esriFieldTypeDate, PE2PTBNu esriFieldTypeString(255), PrjPrntd esriFieldTypeString(255), GeoRqrd esriFieldTypeString(255), GeoInit esriFieldTypeString(255), GeoADate esriFieldTypeDate, TSLRqrd esriFieldTypeString(255), TSLADate esriFieldTypeDate, PrmtRqrd esriFieldTypeString(255), ApSbmtd esriFieldTypeString(255), PrmtDate esriFieldTypeDate,
      PSIRqrd esriFieldTypeString(255), ROWRqrd esriFieldTypeString(255), POLtrSnt esriFieldTypeString(255), ROWSbmtd esriFieldTypeString(255), ROWJobNu esriFieldTypeString(255), RRAgRqrd esriFieldTypeString(255), UtAgRqrd esriFieldTypeString(255), JnAgRqrd esriFieldTypeString(255), LtrUnRqd esriFieldTypeString(255), InLtrRqd esriFieldTypeString(255), Comments esriFieldTypeString(255), ImprvTyp esriFieldTypeString(255), NoROWRqd1 esriFieldTypeSmallInteger, NoROWAqd1 esriFieldTypeSmallInteger, CostEst1 esriFieldTypeInteger, MarkedRoute esriFieldTypeString(200), D6Area esriFieldTypeString(50), DistrictFiscalYear esriFieldTypeSmallInteger, CO_FY esriFieldTypeSmallInteger, ImprovementType esriFieldTypeString(255), GlobalID esriFieldTypeGlobalID(38), Latitude esriFieldTypeDouble, Longitude esriFieldTypeDouble
