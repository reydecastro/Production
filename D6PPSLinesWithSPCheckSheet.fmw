FME workspace D6PPSLinesWithSPCheckSheet.fmw

Readers:
- GEODATABASE_SDE_1: GEODATABASE_SDE

Writers:
- GEODATABASE_SDE_2: GEODATABASE_SDE

DOT_GIS.PPS_D6FilteredLines (reader GEODATABASE_SDE_1)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, County char(200), ImprovementType char(255), Shape.len double
    -> FeatureMerger [REQUESTOR]
DOT_GIS.D6SPCheckSheet (reader GEODATABASE_SDE_1)
    attributes: ApSbmtd char(255), BCRADate date, BCRRqrd char(255), BCRSubmt char(255), BiMoDate date, CEDate date, CntrcNum char(255), CO_FY smallint, Comments char(255), ConsJNum char(255), CostEst1 integer, CstEstT char(255), D6Area char(50), DistrictFiscalYear smallint, DsgnJNum char(255), ECSSubmt char(255), EnvCateg char(255), ESRRqrd char(255), GeoADate date, GeoInit char(255), GeoRqrd char(255), HydApDate date, HydRpRqr char(255), IDSADate date, IDSInit char(255), IDSRqrd char(255), ImprovementType char(255), ImprvTyp char(255), InLtrRqd char(255), JnAgRqrd char(255),
      LOIRqrd char(255), LOISbmtd char(255), LOISDate date, LtrUnRqd char(255), MarkedRoute char(200), NoROWAqd1 smallint, NoROWRqd1 smallint, OBJECTID integer, PE2CName char(255), PE2ICPrj char(255), PE2PDate date, PE2PrComp smallint, PE2PTBNu char(255), PEConNam char(255), PEICPrj char(255), PEPrComp smallint, PEPTBNum char(255), PERADate date, PESADate date, PESAReq char(255), POLtrSnt char(255), PPSNbr char(255), PrjEngr char(255), PrjPrntd char(255), PrmtDate date, PrmtRqrd char(255), PrsntBMo char(255), PSIRqrd char(255), PubInRqd char(255), RdClosur char(255),
      RdClsApr char(255), ROWJobNu char(255), ROWRqrd char(255), ROWSbmtd char(255), RRAgRqrd char(255), SbmtDetr char(255), SctnNum char(255), SigRoute char(255), SPLDate date, SPPSDate date, TeamLdr char(255), TMACompl char(255), TMPAqrd char(255), TMPCompl char(255), TMPRqrd char(255), TSLADate date, TSLRqrd char(255), UPlMuRqd char(255), UpRrjSup char(255), UtAgRqrd char(255)
    -> FeatureMerger [SUPPLIER]
FeatureMerger
    JOIN_KEYS = @Value(PPSNbr) @Value(PPSNbr) AUTO
    SUPPLIERS_FIRST = No
    IGNORE_NULLS = No
    ATTR_ACCUM_MODE = Merge Supplier
    ATTR_CONFLICT_RES = Use Supplier
    MERGE_TYPE = Attributes Only
    PROCESS_DUPS = No
    MERGED -> D6PPSLinesWithSPCheckSheet (writer GEODATABASE_SDE_2)
    NOT_MERGED -> D6PPSLinesWithSPCheckSheet (writer GEODATABASE_SDE_2)
D6PPSLinesWithSPCheckSheet (writer GEODATABASE_SDE_2)
    attributes: AADTYear integer, ADT integer, ApSbmtd char(255), BCRADate date, BCRRqrd char(255), BCRSubmt char(255), BeginMP double, BiMoDate date, CEDate date, CntrcNum char(255), CO_FY integer, Comments char(255), CongressionalDistrict char(20), ConsJNum char(255), CostEst1 integer, County char(200), CRS double, CRSYear integer, CstEstT char(255), CurrentAmount double, D6Area char(50), DistrictFiscalYear integer, DsgnJNum char(255), ECSSubmt char(255), EndMP double, EnvCateg char(255), ESRRqrd char(255), FunctionalClassName char(25), FundDetailAmount char(100), FundSourceDescription char(500),
      FundTypeCode char(100), GeoADate date, GeoInit char(255), GeoRqrd char(255), gisroutekey char(25), HydApDate date, HydRpRqr char(255), IDSADate date, IDSInit char(255), IDSRqrd char(255), ImprovementType char(255), InLtrRqd char(255), JnAgRqrd char(255), LettingDate char(25), Location char(500), LOIRqrd char(255), LOISbmtd char(255), LOISDate date, LtrUnRqd char(255), MarkedRoute char(255), Miles double, Municipality char(255), NoROWAqd1 smallint, NoROWRqd1 smallint, OBJECTID integer, PE2CName char(255), PE2ICPrj char(255), PE2PDate date, PE2PrComp smallint, PE2PTBNu char(255),
      PEConNam char(255), PEICPrj char(255), PEPrComp smallint, PEPTBNum char(255), PERADate date, PESADate date, PESAReq char(255), POLtrSnt char(255), PPSNbr char(25), PrjEngr char(255), PrjPrntd char(255), PrmtDate date, PrmtRqrd char(255), ProjectPublicationId char(50), ProjectPublicationKey char(50), PrsntBMo char(255), PSIRqrd char(255), PubInRqd char(255), RdClosur char(255), RdClsApr char(255), RepresentativeDistrict char(25), ROWJobNu char(255), ROWRqrd char(255), ROWSbmtd char(255), RRAgRqrd char(255), SbmtDetr char(255), SctnNum char(255), Shape_len double, SigRoute char(255), SPLDate date,
      SPPSDate date, StateOrLocalCode char(25), StructureNumber char(255), TeamLdr char(255), TMACompl char(255), TMPAqrd char(255), TMPCompl char(255), TMPRqrd char(255), TSLADate date, TSLRqrd char(255), UPlMuRqd char(255), UpRrjSup char(255), UtAgRqrd char(255)
