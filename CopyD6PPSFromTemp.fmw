FME workspace CopyD6PPSFromTemp.fmw

Readers:
- GEODATABASE_SDE_1: GEODATABASE_SDE

Writers:
- GEODATABASE_SDE_2: GEODATABASE_SDE

DOT_GIS.PPS_D6FilteredPts (reader GEODATABASE_SDE_1)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, County char(200), ImprovementType char(255)
    -> DOT_GIS.PPS_D6FilteredPts (writer GEODATABASE_SDE_2)
DOT_GIS.PPS_D6FilteredPts (writer GEODATABASE_SDE_2)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), ImprovementType char(255), LettingDate char(25), Location char(500), MarkedRoute char(255), Municipality char(255), PPSNbr char(25), ProjectPublicationId char(50), ProjectPublicationKey char(50), RepresentativeDistrict char(25), StateOrLocalCode char(25), StructureNumber char(255), Miles double, County char(200)
DOT_GIS.PPS_D6FilteredLines (reader GEODATABASE_SDE_1)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, County char(200), ImprovementType char(255), Shape.len double
    -> DOT_GIS.PPS_D6FilteredLines (writer GEODATABASE_SDE_2)
DOT_GIS.PPS_D6FilteredLines (writer GEODATABASE_SDE_2)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), ImprovementType char(255), LettingDate char(25), Location char(500), MarkedRoute char(255), Municipality char(255), PPSNbr char(25), ProjectPublicationId char(50), ProjectPublicationKey char(50), RepresentativeDistrict char(25), StateOrLocalCode char(25), StructureNumber char(255), Miles double, County char(200), Shape_len double
DOT_GIS.PPS_D6FilteredEndPts (reader GEODATABASE_SDE_1)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, County char(200), ImprovementType char(255)
    -> DOT_GIS.PPS_D6FilteredEndPts (writer GEODATABASE_SDE_2)
DOT_GIS.PPS_D6FilteredEndPts (writer GEODATABASE_SDE_2)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), ImprovementType char(255), LettingDate char(25), Location char(500), MarkedRoute char(255), Municipality char(255), PPSNbr char(25), ProjectPublicationId char(50), ProjectPublicationKey char(50), RepresentativeDistrict char(25), StateOrLocalCode char(25), StructureNumber char(255), Miles double, County char(200)
