FME workspace SPCheckSheetMergeWithPPS.fmw

Readers:
- GEODATABASE_SDE_1: GEODATABASE_SDE
- GEODATABASE_SDE_2: GEODATABASE_SDE

Writers:
- GEODATABASE_SDE_3: GEODATABASE_SDE

Bookmark: Add new PPS to Check Sheet that are not already there
DOT_GIS.D6SPCheckSheet (reader GEODATABASE_SDE_1)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, MarkedRoute char(200), D6Area char(50), DistrictFiscalYear smallint, CO_FY smallint, ImprovementType char(255)
    -> DuplicateFilter
DuplicateFilter
    KEYATTR = PPSNbr
    INPUT_ORDERED_CHOICE = No
    UNIQUE -> ChangeDetector [ORIGINAL]
    UNIQUE -> FeatureMerger [REQUESTOR]
DOT_GIS.PPS_D6FilteredPts (reader GEODATABASE_SDE_2)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, County char(200), ImprovementType char(255)
    -> DuplicateFilter_2
DuplicateFilter_2
    KEYATTR = PPSNbr
    INPUT_ORDERED_CHOICE = No
    UNIQUE -> ChangeDetector [REVISED]
ChangeDetector
    BLANK_AND_MISSING_DIFFER = Yes
    MATCH_STRATEGY = Match Selected Attributes
    MATCHATTRS = PPSNbr
    LENIENT_MATCH = Yes
    MATCH = NONE
    ADDED -> FeatureMerger [SUPPLIER]
FeatureMerger
    ATTR_ACCUM_MODE = Merge Supplier
    JOIN_KEYS = @Value(PPSNbr) @Value(PPSNbr) AUTO
    IGNORE_NULLS = No
    MERGE_TYPE = Attributes and Geometry
    PROCESS_DUPS = No
    SUPPLIERS_FIRST = Yes
    REJECT_NULL_MISSING_KEYS = No
    ATTR_CONFLICT_RES = Use Requestor
    NOT_MERGED -> DOT_GIS.D6SPCheckSheet (writer GEODATABASE_SDE_3)
    UNREFERENCED -> DOT_GIS.D6SPCheckSheet (writer GEODATABASE_SDE_3)
DOT_GIS.D6SPCheckSheet (writer GEODATABASE_SDE_3)
    attributes: ApSbmtd char(255), BCRADate date, BCRRqrd char(255), BCRSubmt char(255), BiMoDate date, CEDate date, CntrcNum char(255), CO_FY char(5), Comments char(255), ConsJNum char(255), CostEst1 integer, CstEstT char(255), D6Area char(50), DistrictFiscalYear char(5), DsgnJNum char(255), ECSSubmt char(255), EnvCateg char(255), ESRRqrd char(255), GeoADate date, GeoInit char(255), GeoRqrd char(255), HydApDate date, HydRpRqr char(255), IDSADate date, IDSInit char(255), IDSRqrd char(255), ImprovementType char(255), InLtrRqd char(255), JnAgRqrd char(255), LOIRqrd char(255),
      LOISbmtd char(255), LOISDate date, LtrUnRqd char(255), MarkedRoute char(200), NoROWAqd1 smallint, NoROWRqd1 smallint, OBJECTID integer, PE2CName char(255), PE2ICPrj char(255), PE2PDate date, PE2PrComp smallint, PE2PTBNu char(255), PEConNam char(255), PEICPrj char(255), PEPrComp smallint, PEPTBNum char(255), PERADate date, PESADate date, PESAReq char(255), POLtrSnt char(255), PPSNbr char(255), PrjEngr char(255), PrjPrntd char(255), PrmtDate date, PrmtRqrd char(255), PrsntBMo char(255), PSIRqrd char(255), PubInRqd char(255), RdClosur char(255), RdClsApr char(255),
      ROWJobNu char(255), ROWRqrd char(255), ROWSbmtd char(255), RRAgRqrd char(255), SbmtDetr char(255), SctnNum char(255), SigRoute char(255), SPLDate date, SPPSDate date, TeamLdr char(255), TMACompl char(255), TMPAqrd char(255), TMPCompl char(255), TMPRqrd char(255), TSLADate date, TSLRqrd char(255), UPlMuRqd char(255), UpRrjSup char(255), UtAgRqrd char(255)
