FME workspace CopySPCheckSheetFromTemp.fmw

Readers:
- GEODATABASE_SDE_1: GEODATABASE_SDE
- GEODATABASE_SDE_2: GEODATABASE_SDE
- GEODATABASE_SDE_3: GEODATABASE_SDE

Writers:
- GEODATABASE_SDE_4: GEODATABASE_SDE
- GEODATABASE_SDE_5: GEODATABASE_SDE
- GEODATABASE_SDE_6: GEODATABASE_SDE

DOT_GIS.D6SPCheckSheetCopy (reader GEODATABASE_SDE_3) [off]
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, MarkedRoute char(200), D6Area char(50), DistrictFiscalYear smallint, CO_FY smallint
    -> DOT_GIS.D6SPCheckSheet (writer GEODATABASE_SDE_6) [off]
DOT_GIS.D6SPCheckSheet (writer GEODATABASE_SDE_6) [off]
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, MarkedRoute char(200), D6Area char(50), DistrictFiscalYear smallint, CO_FY smallint

Bookmark: Copy Original SP CheckSheet
DOT_GIS.D6SPCheckSheet (reader GEODATABASE_SDE_1)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, MarkedRoute char(200), D6Area char(50), DistrictFiscalYear smallint, CO_FY smallint
    -> DOT_GIS.D6SPCheckSheetCopy (writer GEODATABASE_SDE_4)
DOT_GIS.D6SPCheckSheetCopy (writer GEODATABASE_SDE_4)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, MarkedRoute char(200), D6Area char(50), DistrictFiscalYear smallint, CO_FY smallint

Bookmark: Copy SP CheckSheet from TEMP to Production
DOT_GIS.D6SPCheckSheet (reader GEODATABASE_SDE_2)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, DistrictFiscalYear char(5), CO_FY char(5), MarkedRoute char(200), D6Area char(50)
    -> DOT_GIS.D6SPCheckSheet (writer GEODATABASE_SDE_5)
DOT_GIS.D6SPCheckSheet (writer GEODATABASE_SDE_5)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, DistrictFiscalYear integer, CO_FY integer, MarkedRoute char(200), D6Area char(50)
