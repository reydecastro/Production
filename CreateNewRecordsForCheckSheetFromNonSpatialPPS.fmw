FME workspace CreateNewRecordsForCheckSheetFromNonSpatialPPS.fmw

Parameters:
- DestDataset_TEXTLINE = c:\FMETemp\NewPPS.txt   # Destination Text File
- DestDataset_TEXTLINE_3 = c:\FMETemp\NewPPS.txt   # Destination Text File
- SourceDataset_FILEGDB_3 = c:\FMEtemp\PPS.gdb   # Source Geodatabase

Readers:
- FILEGDB_1: FILEGDB from $(SourceDataset_FILEGDB_3)
- ARCGISONLINEFEATURES_3: ARCGISONLINEFEATURES

Writers:
- TEXTLINE_1: TEXTLINE to $(DestDataset_TEXTLINE)
- TEXTLINE_2: TEXTLINE to $(DestDataset_TEXTLINE_3)
- ARCGISONLINEFEATURES_2: ARCGISONLINEFEATURES

D6SPCheckSheet (reader ARCGISONLINEFEATURES_3)
    attributes: OBJECTID esriFieldTypeOID, PPSNbr esriFieldTypeString(255), PrjEngr esriFieldTypeString(255), TeamLdr esriFieldTypeString(255), CntrcNum esriFieldTypeString(255), DsgnJNum esriFieldTypeString(255), ConsJNum esriFieldTypeString(255), SctnNum esriFieldTypeString(255), SPLDate esriFieldTypeDate, SPPSDate esriFieldTypeDate, CstEstT esriFieldTypeString(255), CEDate esriFieldTypeDate, PEPrComp esriFieldTypeSmallInteger, PEICPrj esriFieldTypeString(255), PEConNam esriFieldTypeString(255), PERADate esriFieldTypeDate, PEPTBNum esriFieldTypeString(255), PrsntBMo esriFieldTypeString(255), BiMoDate esriFieldTypeDate, ESRRqrd esriFieldTypeString(255), ECSSubmt esriFieldTypeString(255), EnvCateg esriFieldTypeString(255), PESAReq esriFieldTypeString(255), PESADate esriFieldTypeDate, HydRpRqr esriFieldTypeString(255), HydApDate esriFieldTypeDate, IDSRqrd esriFieldTypeString(255), IDSInit esriFieldTypeString(255), IDSADate esriFieldTypeDate, BCRRqrd esriFieldTypeString(255),
      BCRSubmt esriFieldTypeString(255), BCRADate esriFieldTypeDate, PubInRqd esriFieldTypeString(255), UPlMuRqd esriFieldTypeString(255), UpRrjSup esriFieldTypeString(255), LOIRqrd esriFieldTypeString(255), LOISbmtd esriFieldTypeString(255), LOISDate esriFieldTypeDate, SigRoute esriFieldTypeString(255), TMPRqrd esriFieldTypeString(255), TMPCompl esriFieldTypeString(255), TMPAqrd esriFieldTypeString(255), TMACompl esriFieldTypeString(255), RdClosur esriFieldTypeString(255), SbmtDetr esriFieldTypeString(255), RdClsApr esriFieldTypeString(255), PE2PrComp esriFieldTypeSmallInteger, PE2ICPrj esriFieldTypeString(255), PE2CName esriFieldTypeString(255), PE2PDate esriFieldTypeDate, PE2PTBNu esriFieldTypeString(255), PrjPrntd esriFieldTypeString(255), GeoRqrd esriFieldTypeString(255), GeoInit esriFieldTypeString(255), GeoADate esriFieldTypeDate, TSLRqrd esriFieldTypeString(255), TSLADate esriFieldTypeDate, PrmtRqrd esriFieldTypeString(255), ApSbmtd esriFieldTypeString(255), PrmtDate esriFieldTypeDate,
      PSIRqrd esriFieldTypeString(255), ROWRqrd esriFieldTypeString(255), POLtrSnt esriFieldTypeString(255), ROWSbmtd esriFieldTypeString(255), ROWJobNu esriFieldTypeString(255), RRAgRqrd esriFieldTypeString(255), UtAgRqrd esriFieldTypeString(255), JnAgRqrd esriFieldTypeString(255), LtrUnRqd esriFieldTypeString(255), InLtrRqd esriFieldTypeString(255), Comments esriFieldTypeString(255), ImprvTyp esriFieldTypeString(255), NoROWRqd1 esriFieldTypeSmallInteger, NoROWAqd1 esriFieldTypeSmallInteger, CostEst1 esriFieldTypeInteger, MarkedRoute esriFieldTypeString(200), D6Area esriFieldTypeString(50), DistrictFiscalYear esriFieldTypeSmallInteger, CO_FY esriFieldTypeSmallInteger, ImprovementType esriFieldTypeString(255), GlobalID esriFieldTypeGlobalID(38), Latitude esriFieldTypeDouble, Longitude esriFieldTypeDouble
    -> FeatureMerger [REQUESTOR]
PPS_D6NonSpatial (reader FILEGDB_1)
    attributes: AADTYear int, ADT int, BeginMP double, CO_FY int, CongressionalDistrict text(20), CRS double, CRSYear int, CurrentAmount double, DistrictFiscalYear int, EndMP double, FunctionalClassName text(25), FundDetailAmount text(100), FundSourceDescription text(500), FundTypeCode text(100), gisroutekey text(25), LettingDate text(25), Location text(500), MarkedRoute text(255), Municipality text(255), PPSNbr text(25), ProjectPublicationId text(50), ProjectPublicationKey text(50), RepresentativeDistrict text(25), StateOrLocalCode text(25), StructureNumber text(255), Miles double, County text(200), OBJECTID objectid, ImprovementType text(255)
    -> FeatureMerger [SUPPLIER]
FeatureMerger
    REJECT_NULL_MISSING_KEYS = Yes
    IGNORE_NULLS = Yes
    PROCESS_DUPS = No
    ATTR_ACCUM_MODE = Merge Supplier
    JOIN_KEYS = @Value(PPSNbr) @Value(PPSNbr) STRING
    MERGE_TYPE = Attributes Only
    ATTR_CONFLICT_RES = Use Requestor
    SUPPLIERS_FIRST = No
    UNREFERENCED -> ListBuilder
    UNREFERENCED -> AttributeRenamer
D6SPCheckSheet (writer ARCGISONLINEFEATURES_2)
    attributes: PPSNbr esriFieldTypeString(255), MarkedRoute esriFieldTypeString(200), DistrictFiscalYear esriFieldTypeSmallInteger, CO_FY esriFieldTypeSmallInteger, ImprovementType esriFieldTypeString(255)
ListBuilder
    LIST_NAME = _list
    GRP_BY = PPSNbr
    -> text_line (writer TEXTLINE_1)
text_line (writer TEXTLINE_1)
    attributes: text_line_data buffer

Bookmark: Create Spatial Data For Non-Spatial PPS
AttributeRenamer
    ATTR_TABLE = RENAME_SET_DEFAULT ImprovementTypeName > ImprvTyp
    -> RandomNumberGenerator
RandomNumberGenerator
    MIN = 0
    RESULT_ATTR = _random_number
    PLACES = 0
    MAX = 250000
    -> AttributeCreator
AttributeCreator
    ATTR_TABLE:
      SET_TO X = -10518146.0367 + @Value(_random_number)
      SET_TO Y = 4688028.8488
      SET_TO LocateStatus = NotLocated
    -> VertexCreator
VertexCreator
    XVAL = @Value(X)
    YVAL = @Value(Y)
    MODE_NAME = Add Point
    -> CoordinateSystemSetter
CoordinateSystemSetter
    COORDSYS = EPSG:3857
    -> D6SPCheckSheet (writer ARCGISONLINEFEATURES_2)

Bookmark: Clear out the text file that stores new PPS
Counter [off]
    CNT_ATTR = _count
    SCOPE = Global
    START = 1
    DOMAIN = counter
    -> Tester [off]
Tester [off]
    BOOL_OP = OR
    TEST_CLAUSE = TEST @Value(_count) = 1
    TEST_DESCRIPTION = ""
    TEST_MODE = Automatic
    PASSED -> AttributeCreator_2 [off]
AttributeCreator_2 [off]
    ATTR_TABLE = SET_TO NoChange
    -> text_line (writer TEXTLINE_2) [off]
text_line (writer TEXTLINE_2) [off]
    attributes: text_line_data buffer

FME custom transformer ListCombiner
Combines lists which have common element(s), and adds the combined list named 
    "_union{}"
    to associated features. Also this transformer adds group ID attribute (0-based sequential number) to the output features, which indicates unique identifier for identical "_union{}".
    The combine processing will be performed with "snowballing". That is, even though List A and List B don't have any common element, they will be combined if List C has a common element to both List A and List B. See also the example below.
    Every element in the "_union{}" list will be unique (no duplicate elements), and the "_union{}" list and original list of the feature have at least one common element.
    If non-list attributes are specified to the "Additional Source Attributes" parameter, their values will be treated as additional elements of the source list during the processing.
    If an input feature does not have specified list and attributes, or they don't store valid values, the feature will be output through the <Rejected> port. 
    Notes
    1) This transformer does not support a nested list and a list containing missing element(s) in the middle of its sequence. If such a list was given, unexpected result could be brought.
    2) This transformer treats every value as a character string. e.g. "1" is distinguished from "01".
    3) This transformer treats <null> as the empty string.
    4) Since this transformer stores all the incoming features in the memory before outputting, it may consume large memory space if too many features were input.
    5) Elements of the "_union{}" list are sorted by the lexicographical order always. Consider using the ListSorter if you need to change the order.
    Example
    Consider a case where these 6 features were input to this transformer. 
    Feature 1: _list{} = [1, 2, 3] 
    Feature 2: _list{} = [3, 4, 5] 
    Feature 3: _list{} = [5, 6, 7] 
    Feature 4: _list{} = [a, b, c] 
    Feature 5: _list{} = [c, d, e] 
    Feature 6: _list{} = [e, f, g] 
    In this case, the transformer creates two combined lists: 
    [A] _union{} = [1, 2, 3, 4, 5, 6, 7] 
    [B] _union{} = [a, b, c, d, e, f, g] 
    and adds [A] to Feature 1, 2, 3; adds [B] to Feature 4, 5, 6. 
    However, if the transformer received one more feature having _list{} = [1, a], all the lists will be combined: 
    _union{} = [1, 2, 3, 4, 5, 6, 7, a, b, c, d, e, f, g] 
    and it will be added to every feature.
Parameters
    Source List
    :
    Select a list that should be processed.
    Additional Source Attributes
    :
    Select attribute(s) that should be treated as additional element(s) of the source list during the processing.
    Ignore Empty and Null
    :
    By default, the transformer ignores the empty string and <null> elements in the source list. Therefore, the "_union{}" list will not contain an empty string by default.
    If you need to treat the empty string as a valid value, set "No" to this parameter. In that case, <null> will be treated as an empty string.
    Group ID Attribute
    :
    Specify an attribute name that will store the group ID.
    Member Count Attribute
    :
    Optionally you can add another attribute that will store the number of members in the group, if you specify an attribute name with this parameter.
    Output Order
    :
    By default ("Keep Input Order"), this transformer outputs features in the same order as inputs. If you set "Ordered by Group ID" to this parameter, output features will be sorted by the group ID.
Copyright (c) 2014-2016 pragmatica inc. 
    Permission is granted to anyone, free of charge, to use, modify and distribute the object code form of this transformer for any purpose, subject to the following restrictions: 
    1) The origin of this transformer and associated FME(R) software must not be misrepresented. 
    2) This transformer may only be used in conjunction with a validly licensed copy of FME software. 
    THIS SOFTWARE IS PROVIDED BY PRAGMATICA INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL PRAGMATICA INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- LIST_ATTR =   # " " Source List
- ADD_ATTRS =   # " " Additional Source Attributes
- IGNORE_EMPTY = Yes   # Ignore Empty and Null
- GROUP_ID_ATTR = _group_id   # Group ID Attribute
- MEMBER_COUNT_ATTR =   # Member Count Attribute
- OUTPUT_ORDER = KEEP_INPUT_ORDER   # Keep Input Order,KEEP_INPUT_ORDER%Ordered by Group ID,ORDER_BY_GROUP Output Order

Input (input)
    -> ParameterFetcher
Note: The TclCaller creates a temporary list attribute containing all source list elements and additional attribute values.
ParameterFetcher
    ATTR_LIST = __listcombiner.list_attr {$(LIST_ATTR)} __listcombiner.add_attrs {$(ADD_ATTRS)} __listcombiner.ignore_empty {$(IGNORE_EMPTY)} __listcombiner.output_order {$(OUTPUT_ORDER)}
    -> TclCaller
TclCaller
    TCLPROG = createList
    SRC:
      proc createList {} {
          set index 0;
          if {[regexp {^(.*\{)(\}.*)$} [FME_GetAttribute "__listcombiner.list_attr"] m front back]} {
              while {1} {
                  set name "$front$index$back";
                  if {[FME_AttributeExists $name]} {
                      FME_SetAttribute "__listcombiner.list{$index}" [FME_GetAttribute $name];
                      incr index;
                  } else {break};
              };
          };
          foreach name [FME_GetAttribute "__listcombiner.add_attrs"] {
              if {[FME_AttributeExists $name]} {
                  FME_SetAttribute "__listcombiner.list{$index}" [FME_GetAttribute $name];
                  incr index;
              };
          };
      }
    VAL_ATTR = __listcombiner.list_attr
    -> PythonCaller
PythonCaller
    HIDE_ATTRIBUTES = __listcombiner.list_attr __listcombiner.add_attrs __listcombiner.ignore_empty __listcombiner.output_order
    PYTHONSYMBOL = ListCombiner
    PYTHONSOURCE:
      import fmeobjects

      # 2014-11-27,  Takashi Iijima,  Original Implementation
      # 2016-01-25,  Takashi Iijima,  Refactoring; Deprecate creating summary features

      class ListCombiner(object):
          def __init__(self):
              # "snowballs" dictioinaly
              # key: value of a list element
              # value: tuple (set of features belonging to a group, set of combined list elements of the group)
              self.snowballs = {}
              self.features = [] # features list keeping the input order.
              self.kAttrIndex = '__listcombiner.index'

          def input(self, feature):
              # Retrieve source list elements and parameter values, and then remove all temporary attributes.
              elements = None
              if not feature.getAttributeNullMissingAndType('__listcombiner.list{0}')[1]:
                  elements = set(feature.getAttribute('__listcombiner.list{}'))
                  if feature.getAttribute('__listcombiner.ignore_empty') == 'Yes':
                      try: elements.remove('')
                      except: pass
              self.orderByGroup = (feature.getAttribute('__listcombiner.output_order') == 'ORDER_BY_GROUP')
              for attr in ['__listcombiner.%s' % s for s in ['list{}', 'list_attr', 'add_attrs', 'ignore_empty', 'output_order']]:
                  feature.removeAttribute(attr)

              # Perform "snowballing" and store the input feature, if more than one valid element exists.
              # Otherwise reject the input feature immediately.
              if elements:
                  group = set([feature])
                  for exGroup, exElements in [self.snowballs[v] for v in elements.copy() if v in self.snowballs]:
                      group |= exGroup
                      elements |= exElements
                  for v in elements:
                      self.snowballs[v] = (group, elements)
                  feature.setAttribute(self.kAttrIndex, len(self.features))
                  self.features.append(feature)
              else:
                  self.pyoutput(feature) # reject

          def close(self):
              groupId = 0
              for group, elements in [self.snowballs[v] for v in sorted(self.snowballs.keys())]:
                  if group:
                      mcount, ulist = len(group), sorted(list(elements))
                      for feat in group:
                          feat.setAttribute('__listcombiner.group_id', groupId)
                          feat.setAttribute('__listcombiner.member_count', mcount)
                          feat.setAttribute('_union{}', ulist)
                      if self.orderByGroup: # output features in the group, in the input order
                          features = {}
                          for feat in group:
                              features[feat.getAttribute(self.kAttrIndex)] = feat
                              feat.removeAttribute(self.kAttrIndex)
                          map(self.pyoutput, [features[i] for i in sorted(features.keys())])
                      # Clear the group so that subsequent iterations for the same group will be skipped.
                      group.clear()
                      groupId += 1
              if not self.orderByGroup: # output all features in the input order
                  for feat in self.features:
                      feat.removeAttribute(self.kAttrIndex)
                      self.pyoutput(feat)
    NEW_ATTRIBUTES = __listcombiner.group_id __listcombiner.member_count _union{}
    -> Tester
Tester
    BOOL_OP = OR
    TEST_CLAUSE = TEST __listcombiner.group_id NOT_ATTRIBUTE_IS_MISSING ""
    TEST_DESCRIPTION = ""
    TEST_MODE = Automatic
    PASSED -> BulkAttributeRenamer
    FAILED -> <Rejected> (output)
Output (output)
<Rejected> (output)

Bookmark: Rename Group ID, Member Count Attribute
BulkAttributeRenamer
    ATTRCHOICE = Selected Attributes
    REPLACE_STR = $(GROUP_ID_ATTR)
    ATTRLIST = __listcombiner.group_id
    REPLACE_PATTERN = .*
    PATTERN_ACTION_DISP = Regular Expression Replace
    -> BulkAttributeRenamer_2
BulkAttributeRenamer_2
    ATTRCHOICE = Selected Attributes
    REPLACE_STR = $(MEMBER_COUNT_ATTR)
    ATTRLIST = __listcombiner.member_count
    REPLACE_PATTERN = .*
    PATTERN_ACTION_DISP = Regular Expression Replace
    -> Output (output)
