FME workspace CopyMergedCheckSheetPPSFromTemp.fmw

Readers:
- GEODATABASE_SDE_1: GEODATABASE_SDE

Writers:
- GEODATABASE_SDE_2: GEODATABASE_SDE

DOT_GIS.D6SPCheckSheetPtsWithPPS (reader GEODATABASE_SDE_1)
    attributes: OBJECTID integer, PPSNbr char(255), PrjEngr char(255), TeamLdr char(255), CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255),
      BCRSubmt char(255), BCRADate date, PubInRqd char(255), UPlMuRqd char(255), UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date,
      PSIRqrd char(255), ROWRqrd char(255), POLtrSnt char(255), ROWSbmtd char(255), ROWJobNu char(255), RRAgRqrd char(255), UtAgRqrd char(255), JnAgRqrd char(255), LtrUnRqd char(255), InLtrRqd char(255), Comments char(255), ImprvTyp char(255), NoROWRqd1 smallint, NoROWAqd1 smallint, CostEst1 integer, CO_FY char(5), MarkedRoute char(200), D6Area char(50), AADTYear integer, ADT integer, BeginMP double, CongressionalDistrict char(20), CRS double, CRSYear integer, CurrentAmount double, EndMP double, FunctionalClassName char(25), FundDetailAmount char(100), FundSourceDescription char(500), FundTypeCode char(100),
      gisroutekey char(25), LettingDate char(25), Location char(500), Municipality char(255), ProjectPublicationId char(50), ProjectPublicationKey char(50), RepresentativeDistrict char(25), StateOrLocalCode char(25), StructureNumber char(255), Miles double, County char(200), DistrictFiscalYear smallint, ImprovementType char(255)
    -> DOT_GIS.D6SPCheckSheetPtsWithPPS (writer GEODATABASE_SDE_2)
DOT_GIS.D6SPCheckSheetPtsWithPPS (writer GEODATABASE_SDE_2)
    attributes: AADTYear integer, ADT integer, ApSbmtd char(255), BCRADate date, BCRRqrd char(255), BCRSubmt char(255), BeginMP double, BiMoDate date, CEDate date, CntrcNum char(255), CO_FY char(5), Comments char(255), CongressionalDistrict char(20), ConsJNum char(255), CostEst1 integer, County char(200), CRS double, CRSYear integer, CstEstT char(255), CurrentAmount double, D6Area char(50), DistrictFiscalYear smallint, DsgnJNum char(255), ECSSubmt char(255), EndMP double, EnvCateg char(255), ESRRqrd char(255), FunctionalClassName char(25), FundDetailAmount char(100), FundSourceDescription char(500),
      FundTypeCode char(100), GeoADate date, GeoInit char(255), GeoRqrd char(255), gisroutekey char(25), HydApDate date, HydRpRqr char(255), IDSADate date, IDSInit char(255), IDSRqrd char(255), ImprovementType char(255), ImprvTyp char(255), InLtrRqd char(255), JnAgRqrd char(255), LettingDate char(25), Location char(500), LOIRqrd char(255), LOISbmtd char(255), LOISDate date, LtrUnRqd char(255), MarkedRoute char(200), Miles double, Municipality char(255), NoROWAqd1 smallint, NoROWRqd1 smallint, OBJECTID integer, PE2CName char(255), PE2ICPrj char(255), PE2PDate date, PE2PrComp smallint,
      PE2PTBNu char(255), PEConNam char(255), PEICPrj char(255), PEPrComp smallint, PEPTBNum char(255), PERADate date, PESADate date, PESAReq char(255), POLtrSnt char(255), PPSNbr char(255), PrjEngr char(255), PrjPrntd char(255), PrmtDate date, PrmtRqrd char(255), ProjectPublicationId char(50), ProjectPublicationKey char(50), PrsntBMo char(255), PSIRqrd char(255), PubInRqd char(255), RdClosur char(255), RdClsApr char(255), RepresentativeDistrict char(25), ROWJobNu char(255), ROWRqrd char(255), ROWSbmtd char(255), RRAgRqrd char(255), SbmtDetr char(255), SctnNum char(255), SigRoute char(255), SPLDate date,
      SPPSDate date, StateOrLocalCode char(25), StructureNumber char(255), TeamLdr char(255), TMACompl char(255), TMPAqrd char(255), TMPCompl char(255), TMPRqrd char(255), TSLADate date, TSLRqrd char(255), UPlMuRqd char(255), UpRrjSup char(255), UtAgRqrd char(255)
DOT_GIS.D6PPSLinesWithSPCheckSheet (reader GEODATABASE_SDE_1)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), ImprovementTypeName char(255), LettingDate char(25), Location char(500), MarkedRoute char(255), Municipality char(255), PPSNbr char(25), ProjectPublicationId char(50), ProjectPublicationKey char(50), RepresentativeDistrict char(25), StateOrLocalCode char(25), StructureNumber char(255), Miles double, PrjEngr char(255), TeamLdr char(255),
      CntrcNum char(255), DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255), BCRSubmt char(255), BCRADate date, PubInRqd char(255), UPlMuRqd char(255),
      UpRrjSup char(255), LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date, PSIRqrd char(255), ROWRqrd char(255), POLtrSnt char(255), ROWSbmtd char(255),
      ROWJobNu char(255), RRAgRqrd char(255), UtAgRqrd char(255), JnAgRqrd char(255), LtrUnRqd char(255), InLtrRqd char(255), Comments char(255), NoROWRqd1 smallint, NoROWAqd1 smallint, CostEst1 integer, D6Area char(50), ImprovementType char(255), SHAPE.len double
    -> DOT_GIS.D6PPSLinesWithSPCheckSheet (writer GEODATABASE_SDE_2)
DOT_GIS.D6PPSLinesWithSPCheckSheet (writer GEODATABASE_SDE_2)
    attributes: OBJECTID integer, AADTYear integer, ADT integer, BeginMP double, CO_FY integer, CongressionalDistrict char(20), CRS double, CRSYear integer, CurrentAmount double, DistrictFiscalYear integer, EndMP double, FunctionalClassName char(25), FundDetailAmount char(100), FundSourceDescription char(500), FundTypeCode char(100), gisroutekey char(25), LettingDate char(25), Location char(500), MarkedRoute char(255), Municipality char(255), PPSNbr char(25), ProjectPublicationId char(50), ProjectPublicationKey char(50), RepresentativeDistrict char(25), StateOrLocalCode char(25), StructureNumber char(255), Miles double, PrjEngr char(255), TeamLdr char(255), CntrcNum char(255),
      DsgnJNum char(255), ConsJNum char(255), SctnNum char(255), SPLDate date, SPPSDate date, CstEstT char(255), CEDate date, PEPrComp smallint, PEICPrj char(255), PEConNam char(255), PERADate date, PEPTBNum char(255), PrsntBMo char(255), BiMoDate date, ESRRqrd char(255), ECSSubmt char(255), EnvCateg char(255), PESAReq char(255), PESADate date, HydRpRqr char(255), HydApDate date, IDSRqrd char(255), IDSInit char(255), IDSADate date, BCRRqrd char(255), BCRSubmt char(255), BCRADate date, PubInRqd char(255), UPlMuRqd char(255), UpRrjSup char(255),
      LOIRqrd char(255), LOISbmtd char(255), LOISDate date, SigRoute char(255), TMPRqrd char(255), TMPCompl char(255), TMPAqrd char(255), TMACompl char(255), RdClosur char(255), SbmtDetr char(255), RdClsApr char(255), PE2PrComp smallint, PE2ICPrj char(255), PE2CName char(255), PE2PDate date, PE2PTBNu char(255), PrjPrntd char(255), GeoRqrd char(255), GeoInit char(255), GeoADate date, TSLRqrd char(255), TSLADate date, PrmtRqrd char(255), ApSbmtd char(255), PrmtDate date, PSIRqrd char(255), ROWRqrd char(255), POLtrSnt char(255), ROWSbmtd char(255), ROWJobNu char(255),
      RRAgRqrd char(255), UtAgRqrd char(255), JnAgRqrd char(255), LtrUnRqd char(255), InLtrRqd char(255), Comments char(255), NoROWRqd1 smallint, NoROWAqd1 smallint, CostEst1 integer, D6Area char(50), ImprovementType char(255), SHAPE_len double
